-- =============================================================
-- Copyright (c) 2004-2009 by H3C Technologies. All rights reserved.
--
-- Description:
-- Reference:
-- Version: V1.1
-- History:
--   V1.0 2009-04-30 Initial Version by jinyi
--   V1.1 2009-12-30 added h3cAccessMediaChanged by jinyi
-- =============================================================
H3C-3GMODEM-MIB DEFINITIONS ::= BEGIN
    IMPORTS
        MODULE-IDENTITY, OBJECT-TYPE, NOTIFICATION-TYPE, Integer32, Unsigned32
            FROM SNMPv2-SMI
        TEXTUAL-CONVENTION
            FROM SNMPv2-TC
        SnmpAdminString
            FROM SNMP-FRAMEWORK-MIB
        h3cCommon
            FROM HUAWEI-3COM-OID-MIB;

h3c3GModem MODULE-IDENTITY
    LAST-UPDATED    "200904301200Z"
    ORGANIZATION
        "Hangzhou H3C Tech. Co., Ltd."
    CONTACT-INFO
        "Platform Team Hangzhou H3C Tech. Co., Ltd.
        Hai-Dian District Beijing P.R. China
        http://www.h3c.com
        Zip:100085
        "
    DESCRIPTION
        "The information about the wireless card and the UIM
         (User Identification Module)."
    REVISION        "200904301200Z"
    DESCRIPTION
        "Initial version of this MIB module."
    ::= { h3cCommon 98 }

H3cUIMStatusType ::= TEXTUAL-CONVENTION
    STATUS      current
    DESCRIPTION
        "The status of the UIM."
    SYNTAX      INTEGER
        {
            absent(1),      -- the UIM is absent
            initial(2),     -- the UIM is initial
            fault(3),       -- something wrong in UIM
            unprotected(4), -- the UIM is not protected with PIN
                            -- (Personal Identification Number) and can be
                            -- used normally
            protected(5),   -- the UIM is protected with PIN and can be
                            -- used normally
            pinLocked(6),   -- the UIM is locked, and need be unlocked with PIN
            pukLocked(7),   -- the UIM is locked, and need be unlocked with PUK
                            -- (PIN Unblocking Key)
            selfDestruct(8) -- the UIM is destruct by itself
        }

h3c3GModemObjects     OBJECT IDENTIFIER ::= { h3c3GModem 1 }

h3cWirelessCard OBJECT IDENTIFIER ::= { h3c3GModemObjects 1 }
h3cUIM OBJECT IDENTIFIER ::= { h3c3GModemObjects 2 }

-- The wireless card table
h3cWirelessCardTable OBJECT-TYPE
    SYNTAX      SEQUENCE OF H3cWirelessCardEntry
    MAX-ACCESS  not-accessible
    STATUS      current
    DESCRIPTION
        "This table contains one row per wireless card."
    ::= { h3cWirelessCard 1 }

h3cWirelessCardEntry OBJECT-TYPE
    SYNTAX      H3cWirelessCardEntry
    MAX-ACCESS  not-accessible
    STATUS      current
    DESCRIPTION
        "Information about a particular wireless card."
    INDEX { h3cWirelessCardIndex }
    ::= { h3cWirelessCardTable 1 }

H3cWirelessCardEntry ::= SEQUENCE
    {
        h3cWirelessCardIndex               Integer32,
        h3cWirelessCardModelName           SnmpAdminString,
        h3cWirelessCardMfgName             SnmpAdminString,
        h3cWirelessCardDescription         SnmpAdminString,
        h3cWirelessCardSerialNumber        SnmpAdminString,
        h3cWirelessCardCMIIID              SnmpAdminString,
        h3cWirelessCardHardwareVersion     SnmpAdminString,
        h3cWirelessCardFirmwareVersion     SnmpAdminString,
        h3cWirelessCardPRLVersion          SnmpAdminString
    }

h3cWirelessCardIndex OBJECT-TYPE
    SYNTAX      Integer32 (1..2147483647)
    MAX-ACCESS  not-accessible
    STATUS      current
    DESCRIPTION
        "The index for this entry."
    ::= { h3cWirelessCardEntry 1 }

h3cWirelessCardModelName OBJECT-TYPE
    SYNTAX      SnmpAdminString
    MAX-ACCESS  read-only
    STATUS      current
    DESCRIPTION
        "The model name of this card."
    ::= { h3cWirelessCardEntry 2 }

h3cWirelessCardMfgName OBJECT-TYPE
    SYNTAX      SnmpAdminString
    MAX-ACCESS  read-only
    STATUS      current
    DESCRIPTION
        "The name of the manufacturer of this card."
    ::= { h3cWirelessCardEntry 3 }

h3cWirelessCardDescription OBJECT-TYPE
    SYNTAX      SnmpAdminString
    MAX-ACCESS  read-only
    STATUS      current
    DESCRIPTION
        "The textual description of this card."
    ::= { h3cWirelessCardEntry 4 }

h3cWirelessCardSerialNumber OBJECT-TYPE
    SYNTAX      SnmpAdminString (SIZE (0..32))
    MAX-ACCESS  read-only
    STATUS      current
    DESCRIPTION
        "The vendor-specific serial number string for this card."
    ::= { h3cWirelessCardEntry 5 }

h3cWirelessCardCMIIID OBJECT-TYPE
    SYNTAX      SnmpAdminString (SIZE (0..32))
    MAX-ACCESS  read-only
    STATUS      current
    DESCRIPTION
        "The card ID of CMII (Ministry of Information Industry of China)."
    ::= { h3cWirelessCardEntry 6 }

h3cWirelessCardHardwareVersion OBJECT-TYPE
    SYNTAX      SnmpAdminString
    MAX-ACCESS  read-only
    STATUS      current
    DESCRIPTION
        "The vendor-specific hardware version string for this card."
    ::= { h3cWirelessCardEntry 7 }

h3cWirelessCardFirmwareVersion OBJECT-TYPE
    SYNTAX      SnmpAdminString
    MAX-ACCESS  read-only
    STATUS      current
    DESCRIPTION
        "The vendor-specific firmware version string for this card."
    ::= { h3cWirelessCardEntry 8 }

h3cWirelessCardPRLVersion OBJECT-TYPE
    SYNTAX      SnmpAdminString
    MAX-ACCESS  read-only
    STATUS      current
    DESCRIPTION
        "The preferred roaming list version for this card."
    ::= { h3cWirelessCardEntry 9 }

-- The UIM information table
h3cUIMInfoTable OBJECT-TYPE
    SYNTAX      SEQUENCE OF H3cUIMInfoEntry
    MAX-ACCESS  not-accessible
    STATUS      current
    DESCRIPTION
        "This table contains one row per UIM."
    ::= { h3cUIM 1 }

h3cUIMInfoEntry OBJECT-TYPE
    SYNTAX      H3cUIMInfoEntry
    MAX-ACCESS  not-accessible
    STATUS      current
    DESCRIPTION
        "The information about the UIM."
    INDEX { h3cWirelessCardIndex, h3cUIMIndex }
    ::= { h3cUIMInfoTable 1 }

H3cUIMInfoEntry ::= SEQUENCE
    {
        h3cUIMIndex          Integer32,
        h3cUIMStatus         H3cUIMStatusType,
        h3cUIMImsi           SnmpAdminString,
        h3cUIMPin            SnmpAdminString,
        h3cUIMVoltage        Unsigned32,
        h3cUIMProvider       SnmpAdminString,
        h3cUIMSignal         Integer32,
        h3cUIMTryPinPukTimes Unsigned32,
        h3cUIMOldPin         SnmpAdminString
    }

h3cUIMIndex OBJECT-TYPE
    SYNTAX      Integer32 (0..2147483647)
    MAX-ACCESS  not-accessible
    STATUS      current
    DESCRIPTION
        "The index for this entry."
    ::= { h3cUIMInfoEntry 1 }

h3cUIMStatus OBJECT-TYPE
    SYNTAX      H3cUIMStatusType
    MAX-ACCESS  read-only
    STATUS      current
    DESCRIPTION
        "The status about this UIM."
    ::= { h3cUIMInfoEntry 2 }

h3cUIMImsi OBJECT-TYPE
    SYNTAX      SnmpAdminString (SIZE (0..32))
    MAX-ACCESS  read-only
    STATUS      current
    DESCRIPTION
        "The IMSI (International Mobile Subscriber Identification Number) about
        this UIM.  If this information is unknown to the agent, then this object
        will be returned a zero-length string."
    ::= { h3cUIMInfoEntry 3 }

h3cUIMPin OBJECT-TYPE
    SYNTAX      SnmpAdminString (SIZE (0..9))
    MAX-ACCESS  read-only
    STATUS      current
    DESCRIPTION
        "The PIN about this UIM.  If this information is unknown to the agent,
        then this object will be returned a zero-length string."
    ::= { h3cUIMInfoEntry 4 }

h3cUIMVoltage OBJECT-TYPE
    SYNTAX      Unsigned32(0..4294967295)
    UNITS       "milli-volt"
    MAX-ACCESS  read-only
    STATUS      current
    DESCRIPTION
        "The voltage about this UIM.  If this information is unknown to the
        agent, then this object will be returned 4294967295."
    ::= { h3cUIMInfoEntry 5 }

h3cUIMProvider OBJECT-TYPE
    SYNTAX      SnmpAdminString (SIZE (0..32))
    MAX-ACCESS  read-only
    STATUS      current
    DESCRIPTION
        "The provider of mobile network.  If this information is unknown to the
        agent, then this object will be returned a zero-length string."
    ::= { h3cUIMInfoEntry 6 }

h3cUIMSignal OBJECT-TYPE
    SYNTAX      Integer32(0..31 | 99)
    MAX-ACCESS  read-only
    STATUS      current
    DESCRIPTION
        "The intensity of the signal about this UIM.
        A value of '99' means no signal."
    ::= { h3cUIMInfoEntry 7 }

h3cUIMTryPinPukTimes OBJECT-TYPE
    SYNTAX      Unsigned32(0..4294967295)
    MAX-ACCESS  read-only
    STATUS      current
    DESCRIPTION
        "The number of remaining times for unlocking PIN or PUK.
        The value is associated the same instance of h3cUIMStatus.  If this
        information is unknown to the agent, then this object will be
        returned 4294967295."
    ::= { h3cUIMInfoEntry 8 }

h3cUIMOldPin OBJECT-TYPE
    SYNTAX      SnmpAdminString (SIZE (0..9))
    MAX-ACCESS  accessible-for-notify
    STATUS      current
    DESCRIPTION
            "The old PIN for this UIM."
    ::= { h3cUIMInfoEntry 9 }

-- MIB trap definitions
h3c3GModemTrap       OBJECT IDENTIFIER ::= { h3c3GModem 2 }
h3c3GModemTraps       OBJECT IDENTIFIER ::= { h3c3GModem 3 }
h3c3GModemTrapPrefix  OBJECT IDENTIFIER ::= { h3c3GModemTraps 0 }

h3cDevSerialNumber OBJECT-TYPE
    SYNTAX      SnmpAdminString (SIZE (0..32))
    MAX-ACCESS  accessible-for-notify
    STATUS      current
    DESCRIPTION
            "The serial number of the current device."
    ::= { h3c3GModemTrap 1 }

h3cDeviceOUI OBJECT-TYPE
    SYNTAX      SnmpAdminString (SIZE (0..64))
    MAX-ACCESS  accessible-for-notify
    STATUS      current
    DESCRIPTION
            "The OUI (Organizational Unique Identifier) of the current device."
    ::= { h3c3GModemTrap 2 }

h3cAccessMedia OBJECT-TYPE
    SYNTAX      INTEGER
        {
            unknown(1),
            air(2),
            cable(3)
        }
    MAX-ACCESS  accessible-for-notify
    STATUS      current
    DESCRIPTION
            "The current access media."
    ::= { h3c3GModemTrap 3 }

h3cWirelessCardInserted NOTIFICATION-TYPE
    OBJECTS
        {
            h3cDeviceOUI,
            h3cDevSerialNumber,
            h3cWirelessCardSerialNumber,
            h3cUIMImsi
        }
    STATUS      current
    DESCRIPTION
        "A h3cWirelessCardInserted notification is generated when a wireless
        card is inserted."
   ::= { h3c3GModemTrapPrefix 1 }

h3cWirelessCardPulledOut NOTIFICATION-TYPE
    OBJECTS
        {
            h3cDeviceOUI,
            h3cDevSerialNumber,
            h3cWirelessCardSerialNumber,
            h3cUIMImsi
        }
    STATUS      current
    DESCRIPTION
        "A h3cWirelessCardPulledOut notification is generated when a wireless
        card is pulled out."
   ::= { h3c3GModemTrapPrefix 2 }

h3cUIMPinInvalid NOTIFICATION-TYPE
    OBJECTS
        {
            h3cDeviceOUI,
            h3cDevSerialNumber,
            h3cWirelessCardSerialNumber,
            h3cUIMImsi
        }
    STATUS      current
    DESCRIPTION
        "A h3cUIMPinInvalid notification is generated when UIM PIN is invalid."
   ::= { h3c3GModemTrapPrefix 3 }

h3cUIMPinChanged NOTIFICATION-TYPE
    OBJECTS
        {
            h3cDeviceOUI,
            h3cDevSerialNumber,
            h3cWirelessCardSerialNumber,
            h3cUIMImsi,
            h3cUIMOldPin,
            h3cUIMPin
        }
    STATUS      current
    DESCRIPTION
        "A h3cUIMPinInvalid notification is generated when UIM PIN is changed."
   ::= { h3c3GModemTrapPrefix 4 }

h3cAccessMediaChanged NOTIFICATION-TYPE
    OBJECTS
        {
            h3cDeviceOUI,
            h3cDevSerialNumber,
            h3cWirelessCardSerialNumber,
            h3cUIMImsi,
            h3cAccessMedia
        }
    STATUS      current
    DESCRIPTION
        "A h3cAccessMediaChanged notification is generated when access media
         is changed."
   ::= { h3c3GModemTrapPrefix 5 }
END
