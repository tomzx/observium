-- =================================================================
-- Copyright (c) 2004-2011 Hangzhou H3C Tech. Co., Ltd. All rights reserved.
--
-- Description: Description Of Portal
-- Reference:
-- Version: V1.3
-- History:
--   V1.0 2008-12-30, Created by d04528
--   V1.1 2009-4-30, Modified by h02978
--        Added node h3cPortalServerPort
--        Added table h3cPortalIfInfoTable, including the following nodes,
--            h3cPortalAuthReqNumber
--            h3cPortalAuthSuccNumber
--            h3cPortalAuthFailNumber
--        Added trap node h3cPortalServerGet
--   V1.2 2010-5-31, Modified by y07111
--        Added table h3cPortalIfServerTable, including the following nodes,
--            h3cPortalIfServerIndex
--            h3cPortalIfServerUrl
--            h3cPortalIfServerRowStatus
--        Added h3cPortalNasId
--   V1.3 2010-11-8, Modified by y07111
--        Added table h3cPortalStatistic,including the following nodes,
--        h3cPortalStatAuthReq
--        h3cPortalStatAckLogout
--        h3cPortalStatNotifyLogout
--        h3cPortalStatChallengeTimeout
--        h3cPortalStatChallengeBusy
--        h3cPortalStatChallengeFail
--        h3cPortalStatAuthTimeout
--        h3cPortalStatAuthFail
--        h3cPortalStatPwdError
--        h3cPortalStatAuthBusy
--        h3cPortalStatAuthDisordered
--        h3cPortalStatAuthUnknownError
-- =================================================================
H3C-PORTAL-MIB DEFINITIONS ::= BEGIN
IMPORTS
    h3cCommon
        FROM HUAWEI-3COM-OID-MIB
    OBJECT-TYPE, NOTIFICATION-TYPE, MODULE-IDENTITY, Integer32, Counter64
        FROM SNMPv2-SMI
    RowStatus
        FROM SNMPv2-TC
    ifIndex
        FROM RFC1213-MIB;

h3cPortal MODULE-IDENTITY
    LAST-UPDATED "201011080000Z"            -- November 8th, 2010 at 00:00 GMT
    ORGANIZATION
        "Hangzhou H3C Tech. Co., Ltd."
    CONTACT-INFO
        "Platform Team Hangzhou H3C Tech. Co., Ltd.
        Hai-Dian District Beijing P.R. China
        http://www.h3c.com
        Zip:100085
        "
    DESCRIPTION
        "The MIB module is used for managing portal."
    ::= { h3cCommon 99 }


h3cPortalConfig OBJECT IDENTIFIER ::= { h3cPortal 1 }

--
-- PORTAL MAX USER NUMBER
--

h3cPortalMaxUserNumber OBJECT-TYPE
    SYNTAX      Integer32
    MAX-ACCESS  read-write
    STATUS      current
    DESCRIPTION
        "Specify the maximum number of online users,
        the value to be set should meet the following two conditions:
        1. Less than or equal to h3cPortalUserNumberUpperLimit.
        2. Greater than or equal to one.

        The default value is equal to h3cPortalUserNumberUpperLimit."
    ::= { h3cPortalConfig 1 }

--
-- PORTAL CURRENT USER NUMBER
--

h3cPortalCurrentUserNumber OBJECT-TYPE
    SYNTAX      Integer32
    MAX-ACCESS  read-only
    STATUS      current
    DESCRIPTION
        "The current number of users connecting to the portal."
    ::= { h3cPortalConfig 2 }

--
-- PORTAL STATUS
--

h3cPortalStatus OBJECT-TYPE
    SYNTAX      INTEGER
    {
         enabled(1),
         disabled(2)
    }
    MAX-ACCESS  read-only
    STATUS      current
    DESCRIPTION
        "It indicates the portal status.
         enabled:
            Portal is enabled on one or more interfaces.
         disabled:
            Portal is not enabled on any interface."
    ::= { h3cPortalConfig 3 }

--
-- PORTAL USER NUMBER_UPPER_LIMIT
--

h3cPortalUserNumberUpperLimit OBJECT-TYPE
    SYNTAX      Integer32
    MAX-ACCESS  read-only
    STATUS      current
    DESCRIPTION
        "The upper limit of h3cPortalMaxUserNumber."
    ::= { h3cPortalConfig 4 }

--
-- PORTAL NAS-ID Config
--
h3cPortalNasId OBJECT-TYPE
    SYNTAX      OCTET STRING
    MAX-ACCESS  read-write
    STATUS      current
    DESCRIPTION
        "The nas id of this device."
    ::= { h3cPortalConfig 5 }

--
-- PORTAL TABLES
--

h3cPortalTables OBJECT IDENTIFIER ::= { h3cPortal 2 }


--
-- PORTAL server table
--
h3cPortalServerTable OBJECT-TYPE
    SYNTAX      SEQUENCE OF H3cPortalServerEntry
    MAX-ACCESS  not-accessible
    STATUS      current
    DESCRIPTION
        "This table defines the name and URL of portal server.
        It can not be created and destroyed by MIB."
    ::= { h3cPortalTables 1 }

h3cPortalServerEntry OBJECT-TYPE
    SYNTAX      H3cPortalServerEntry
    MAX-ACCESS  not-accessible
    STATUS      current
    DESCRIPTION
        "There is a row in this table for each name and URL of portal server.
        It is indexed using the object h3cPortalServerName."
    INDEX
        {
            h3cPortalServerName
        }
    ::= { h3cPortalServerTable 1 }


H3cPortalServerEntry ::= SEQUENCE
    {
        h3cPortalServerName               OCTET STRING,
        h3cPortalServerUrl                OCTET STRING,
        h3cPortalServerPort               Integer32
    }

h3cPortalServerName OBJECT-TYPE
    SYNTAX      OCTET STRING (SIZE (1..32))
    MAX-ACCESS  accessible-for-notify
    STATUS      current
    DESCRIPTION
        "It is the index of the table of h3cPortalServerTable, it shows
        the name of the portal server."
    ::= { h3cPortalServerEntry 1 }

h3cPortalServerUrl OBJECT-TYPE
    SYNTAX      OCTET STRING (SIZE (1..127))
    MAX-ACCESS  read-write
    STATUS      current
    DESCRIPTION
        "It shows the uniform resource locator to the portal server.
        Users which have not logon to portal will be redirected to the
        portal server according to h3cPortalServerUrl.

        The value is consisted of protocol, IP address and relative path.
        For example: HTTP://10.1.1.1/portal

        It is not configurable when the portal server has been enabled."
    ::= { h3cPortalServerEntry 2 }

h3cPortalServerPort OBJECT-TYPE
    SYNTAX      Integer32 (1..65534)
    MAX-ACCESS  read-write
    STATUS      current
    DESCRIPTION
        "It shows the UDP port of the portal server.

        The port will be used when client sends packets to portal server.
        Default value is 50100.

        It is not configurable when the portal server has been enabled."
    ::= { h3cPortalServerEntry 3 }

--
-- PORTAL If Info Table
--
h3cPortalIfInfoTable OBJECT-TYPE
    SYNTAX      SEQUENCE OF H3cPortalIfInfoEntry
    MAX-ACCESS  not-accessible
    STATUS      current
    DESCRIPTION
        "This table describes the portal information on some interface."
    ::= { h3cPortalTables 2 }

h3cPortalIfInfoEntry OBJECT-TYPE
    SYNTAX      H3cPortalIfInfoEntry
    MAX-ACCESS  not-accessible
    STATUS      current
    DESCRIPTION
        "There is a row in this table for a interface on which
        portal has been enabled.
        It is indexed using the object ifIndex."
    INDEX
        {
            ifIndex
        }
    ::= { h3cPortalIfInfoTable 1 }


H3cPortalIfInfoEntry ::= SEQUENCE
    {
        h3cPortalAuthReqNumber            Integer32,
        h3cPortalAuthSuccNumber           Integer32,
        h3cPortalAuthFailNumber           Integer32
    }

h3cPortalAuthReqNumber OBJECT-TYPE
    SYNTAX      Integer32
    MAX-ACCESS  read-only
    STATUS      current
    DESCRIPTION
        "It shows the number of authentication request messages
        which are sent by portal module to AAA module."
    ::= { h3cPortalIfInfoEntry 1 }


h3cPortalAuthSuccNumber OBJECT-TYPE
    SYNTAX      Integer32
    MAX-ACCESS  read-only
    STATUS      current
    DESCRIPTION
        "It shows the number of authentication success response messages
        which are sent by AAA module to portal module."
    ::= { h3cPortalIfInfoEntry 2 }

h3cPortalAuthFailNumber OBJECT-TYPE
    SYNTAX      Integer32
    MAX-ACCESS  read-only
    STATUS      current
    DESCRIPTION
        "It shows the number of authentication failure response messages
        which are sent by AAA module to portal module."
    ::= { h3cPortalIfInfoEntry 3 }

--
-- PORTAL If Config Table
--
h3cPortalIfServerTable OBJECT-TYPE
    SYNTAX      SEQUENCE OF H3cPortalIfServerEntry
    MAX-ACCESS  not-accessible
    STATUS      current
    DESCRIPTION
        "This table describes the portal information on some interface."
    ::= { h3cPortalTables 3 }

h3cPortalIfServerEntry OBJECT-TYPE
    SYNTAX      H3cPortalIfServerEntry
    MAX-ACCESS  not-accessible
    STATUS      current
    DESCRIPTION
        "There is a row in this table for a interface on which
        portal has been enabled.
        It is indexed using the object ifIndex."
    INDEX
        {
            h3cPortalIfServerIndex
        }
    ::= { h3cPortalIfServerTable 1 }

H3cPortalIfServerEntry ::= SEQUENCE
    {
        h3cPortalIfServerIndex                   Integer32,
        h3cPortalIfServerUrl                     OCTET STRING,
        h3cPortalIfServerRowStatus               RowStatus
    }

h3cPortalIfServerIndex  OBJECT-TYPE
    SYNTAX      Integer32
    MAX-ACCESS  not-accessible
    STATUS      current
    DESCRIPTION
        "It is the index of the table of h3cIfPtServerTable, it shows
        the index of the portal server."
    ::={ h3cPortalIfServerEntry 1 }

h3cPortalIfServerUrl OBJECT-TYPE
    SYNTAX      OCTET STRING
    MAX-ACCESS  read-create
    STATUS      current
    DESCRIPTION
        "It shows the uniform resource locator to the portal server.
        Users which have not logon to portal will be redirected to the
        portal server according to h3cPortalServerIfUrl.
        The value is consisted of protocol, IP address and relative path.
        For example: HTTP://10.1.1.1/portal
        It is not configurable when the portal server has been enabled."
    ::= { h3cPortalIfServerEntry 2 }

h3cPortalIfServerRowStatus OBJECT-TYPE
    SYNTAX   RowStatus
    MAX-ACCESS  read-create
    STATUS      current
    DESCRIPTION
        "This object is responsible for managing the creation, deletion and
        modification of rows, which support active status and CreateAndGo,
        Destroy operation.  To create a new row, portal server must be specified.
        To destroy an existent row, the portal server MUST NOT be referred by
        interface."
    ::= { h3cPortalIfServerEntry 3 }

--
-- Define the portal Traps.
--

h3cPortalTraps OBJECT IDENTIFIER ::= { h3cPortal 3 }

h3cPortalTrapPrefix OBJECT IDENTIFIER ::= { h3cPortalTraps 0 }

h3cPortalServerLost NOTIFICATION-TYPE
    OBJECTS
        {
            h3cPortalServerName
        }
    STATUS      current
    DESCRIPTION
        "This trap is generated when the device finds that the portal server
        is unreachable, the portal server's name is h3cPortalServerName,
        and the portal server has been enabled."
    ::= { h3cPortalTrapPrefix 1 }

h3cPortalServerGet NOTIFICATION-TYPE
    OBJECTS
        {
            h3cPortalServerName
        }
    STATUS      current
    DESCRIPTION
        "This trap is generated when the device finds that the state of portal
        server changes from unreachable state to reachable,
        the portal server's name is h3cPortalServerName,
        and the portal server has been enabled."
    ::= { h3cPortalTrapPrefix 2 }

-- PORTAL STATISTIC

h3cPortalStatistic OBJECT IDENTIFIER ::= { h3cPortal 4 }

-- PORTAL AUTH REQ STATISTIC

h3cPortalStatAuthReq OBJECT-TYPE
    SYNTAX      Counter64
    MAX-ACCESS  read-only
    STATUS      current
    DESCRIPTION
        "It shows the total number of portal authentication requests from the
        portal server."
    ::= { h3cPortalStatistic 1 }

-- PORTAL ACK LOGOUT STATISTIC

h3cPortalStatAckLogout OBJECT-TYPE
    SYNTAX      Counter64
    MAX-ACCESS  read-only
    STATUS      current
    DESCRIPTION
        "It shows the number of logout requests from the portal server."
    ::= { h3cPortalStatistic 2 }

-- PORTAL NOTIFY LOGOUT STATISTIC

h3cPortalStatNotifyLogout OBJECT-TYPE
    SYNTAX      Counter64
    MAX-ACCESS  read-only
    STATUS      current
    DESCRIPTION
        "It shows the number of logout requests from the access device."
    ::= { h3cPortalStatistic 3 }

-- PORTAL CHALLENGE TIMEOUT STATISTIC

h3cPortalStatChallengeTimeout OBJECT-TYPE
    SYNTAX      Counter64
    MAX-ACCESS  read-only
    STATUS      current
    DESCRIPTION
        "It shows the number of challenge from the portal server without
        response."
    ::= { h3cPortalStatistic 4 }

-- PORTAL CHALLENGE BUSY STATISTIC

h3cPortalStatChallengeBusy OBJECT-TYPE
    SYNTAX      Counter64
    MAX-ACCESS  read-only
    STATUS      current
    DESCRIPTION
        "It shows the number of device-busy responses for challenges from
        the portal server."
    ::= { h3cPortalStatistic 5 }

-- PORTAL CHALLENGE FAIL STATISTIC

h3cPortalStatChallengeFail OBJECT-TYPE
    SYNTAX      Counter64
    MAX-ACCESS  read-only
    STATUS      current
    DESCRIPTION
        "It shows the number of challenges from the portal server with
        failure response."
    ::= { h3cPortalStatistic 6 }

-- PORTAL authenticate TIMEOUT STATISTIC

h3cPortalStatAuthTimeout OBJECT-TYPE
    SYNTAX      Counter64
    MAX-ACCESS  read-only
    STATUS      current
    DESCRIPTION
        "It shows the number of authentication requests from the portal
        server without responses."
    ::= { h3cPortalStatistic 7 }

-- PORTAL authenticate FAIL STATISTIC

h3cPortalStatAuthFail OBJECT-TYPE
    SYNTAX      Counter64
    MAX-ACCESS  read-only
    STATUS      current
    DESCRIPTION
        "It shows the number of authentication requests from the portal
        server with failure responses."
    ::= { h3cPortalStatistic 8 }

-- PORTAL PASSWORD ERROR STATISTIC

h3cPortalStatPwdError OBJECT-TYPE
    SYNTAX      Counter64
    MAX-ACCESS  read-only
    STATUS      current
    DESCRIPTION
        "It shows the number of password errors."
    ::= { h3cPortalStatistic 9 }

-- PORTAL authenticate BUSY STATISTIC

h3cPortalStatAuthBusy OBJECT-TYPE
    SYNTAX      Counter64
    MAX-ACCESS  read-only
    STATUS      current
    DESCRIPTION
        "It shows the number of device-busy responses to authentication
        requests from the portal server."
    ::= { h3cPortalStatistic 10 }

-- PORTAL authenticate DISORDER STATISTIC

h3cPortalStatAuthDisordered OBJECT-TYPE
    SYNTAX      Counter64
    MAX-ACCESS  read-only
    STATUS      current
    DESCRIPTION
        "It shows the number of disordered authentication packets from
        the portal server."
    ::= { h3cPortalStatistic 11 }

-- PORTAL authenticate UNKNOWN ERROR STATISTIC

h3cPortalStatAuthUnknownError OBJECT-TYPE
    SYNTAX      Counter64
    MAX-ACCESS  read-only
    STATUS      current
    DESCRIPTION
        "It shows the number of unknown errors."
    ::= { h3cPortalStatistic 12 }

END
